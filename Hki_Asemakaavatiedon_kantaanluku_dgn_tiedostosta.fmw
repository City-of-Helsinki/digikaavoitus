FME workspace Hki_Asemakaavatiedon_kantaanluku_dgn_tiedostosta.fmw
Title: Ajantasa-asemakaava-aineiston luokittelu
Description: Aineiston yhtenäinen luokittelu WMS-julkaisua varten. Vienti PostGis-tietokantaan.
Usage: Avoimen lisenssin ehdoin, tarkentuu.
History: 20.10.2015,Mari Raussi / Sito,Irrotettu ensimmäinen versio yhteiseen käyttöön.

Parameters:
- SourceDataset_DGNV8XFM_3 = $(FME_MF_DIR)0845_2_Koivusaari_asemakaavaluonnos_2000_13012017.dgn   # Source Bentley MicroStation Design File(s)
- FEATURE_TYPES_2 =
- DestDataset_POSTGIS_17 = maankayttopaatokset   # Connection
- DestDataset_POSTGIS_13 = maankayttopaatokset   # Connection
- DestDataset_POSTGIS_11 = maankayttopaatokset   # Connection
- DestDataset_POSTGIS_15 = maankayttopaatokset   # Connection
- DestDataset_POSTGIS_19 = maankayttopaatokset   # Connection
- DestDataset_POSTGIS_12 = maankayttopaatokset   # Connection
- DestDataset_POSTGIS_14 = maankayttopaatokset   # Connection
- DestDataset_POSTGIS_16 = maankayttopaatokset   # Connection
- DestDataset_POSTGIS_18 = maankayttopaatokset   # Connection

Readers:
- DGNV8XFM_1: DGNV8XFM from $(SourceDataset_DGNV8XFM_3) in EPSG:3879

Writers:
- POSTGIS_1: POSTGIS to $(DestDataset_POSTGIS_17) in EPSG:3879
- POSTGIS_2: POSTGIS to $(DestDataset_POSTGIS_13) in EPSG:3879
- POSTGIS_3: POSTGIS to $(DestDataset_POSTGIS_11) in EPSG:3879
- POSTGIS_4: POSTGIS to $(DestDataset_POSTGIS_15) in EPSG:3879
- POSTGIS_5: POSTGIS to $(DestDataset_POSTGIS_19) in EPSG:3879
- POSTGIS_6: POSTGIS to $(DestDataset_POSTGIS_12) in EPSG:3879
- POSTGIS_7: POSTGIS to $(DestDataset_POSTGIS_18) in EPSG:3879
- POSTGIS_8: POSTGIS to $(DestDataset_POSTGIS_14) in EPSG:3879
- POSTGIS_9: POSTGIS to $(DestDataset_POSTGIS_16) in EPSG:3879

AK_TonttiRaja (reader DGNV8XFM_1)
    attributes: YhtDatanLuoja char(8), YhtDatanOmistaja char(13), YhtLuontiPvm char(9), poistettava char(6), sitova char(7), Yksikko number(2,0), lisakm2 number(2,0), Sijaintialue number(2,0), knumerokartalle char(6), kerrosluku number(2,0), vanhakohde char(6), Muokattu char(5), k number(2,0), kaytettykm2 number(2,0), kaavanvaihe char(15), km2 number(2,0), hyvaksyja number(2,0), pintaala number(14,6), kaavanlaatija number(2,0), kaavanimi1 number(2,0), lisakm2kuvaus number(2,0), nahtavillealkupvm char(9), lisakm2rivita char(3), YhtDatanMuokkaaja char(8), nahtavillaviimpvm char(9), kaavatyyppi char(11), kaavamerkinta char(3), yhteensakm2 number(2,0), kieli1 char(6), kaavanimi2 number(2,0),
      maanalainen char(6), Kunta number(4,0), hyvaksymispvm char(9), varisavy number(2,0), tehokkuusluku number(2,0), korttelinnumero number(2,0), Skaalattu char(5), u number(2,0), kayttotarkoitus char(26), Hankenumero number(2,0), kaavatyyppi2 number(2,0), teksti char(11), kuntakoodi number(4,0), lisatietoja number(5,0), voimaantulopvm char(9), Ryhma number(2,0), kaavatunnus number(2,0), kieli2 char(6), YhtMuokkausPvm char(9), aluesijainti char(20), vireilletulopvm char(9), tyyppi char(20), kaavamaarayskirjasto char(73)
    -> GeometryFilter_5
Note: Jaotellaan kohteet igds_xfm_namen mukaan
AttributeFilter_7
    ATTR_NAME = igds_xfm_name
    ATTR_VALUES = AK_AsemakaavaViiva,AK_KayttotarkoitusViiva,AK_KayttotarkoitusSymboliViiva,AK_RakennusalaViiva,AK_TonttiRaja,AK_RakentaminenViiva,AK_YmparistoViiva,AK_LiikennointiViiva,AK_JohdoillevarattuViiva,AK_MuuAsemakaavaViiva,AK_OmaViiva,<EMPTY>,<MISSING>,<NULL>,<UNFILTERED>
    AK_AsemakaavaViiva -> TestFilter_4
    AK_KayttotarkoitusViiva -> TestFilter_Visualisointi_-__AttributeKeeper
    AK_KayttotarkoitusSymboliViiva -> TestFilter_Visualisointi_-__AttributeKeeper
    AK_RakennusalaViiva -> AttributeFilter_7_AK_RakennusalaViiva_-__SpatialFilter_Candidate
    AK_TonttiRaja -> TestFilter_Visualisointi_-__AttributeKeeper
    AK_RakentaminenViiva -> AttributeFilter_7_AK_RakennusalaViiva_-__SpatialFilter_Candidate
    AK_YmparistoViiva -> AttributeFilter_2_AK_YmparistoSymboli_-__SpatialFilter_2_Candidate
    AK_LiikennointiViiva -> AttributeFilter_7_AK_JohdoillevarattuViiva_-__AttributeKeeper_3
    AK_JohdoillevarattuViiva -> AttributeFilter_7_AK_JohdoillevarattuViiva_-__AttributeKeeper_3
    AK_MuuAsemakaavaViiva -> TestFilter
    AK_OmaViiva -> TestFilter_3
    <UNFILTERED> -> TestFilter_Visualisointi_-__AttributeKeeper
AreaBuilder
    CONSIDER_NODE_ELEVATION = no
    POLY_ACCUM_ATTRS_NAME = Use Attributes From One Feature
    DONUT_CREATION = Yes
    ALLOW_CYCLES = No
    POLY_LIST_ATTRS_TO_INCLUDE_MODE = Selected Attributes
    CONNECT_Z_MODE = First Wins
    CHECK_CURVE_DIRECTION = No
    SNAP_TOLERANCE = 0
    SNAPTYPE_PARAM = None
    DROP_HOLES = No
    LINES_AS_SEGMENTS = No
    AREA -> TestFilter_3_Valitus_-__asemakaavat.valitus
AttributeCreator_2_OUTPUT: Junction
    -> yleinen_tai_muu_alue (writer POSTGIS_3)
AttributeRenamer_4
    ATTR_TABLE = RENAME_SET_DEFAULT yleinen_tai_muu_alue_uuid > korttelialue_uuid
    -> FeatureMerger_2 [SUPPLIER]
    -> korttelialue (writer POSTGIS_2)
AttributeRenamer_6_OUTPUT_-__DuplicateFilter: Junction
    -> DuplicateFilter
    -> FeatureMerger_3 [REQUESTOR]
    -> SpatialFilter [Filter]
DuplicateFilter
    INPUT_ORDERED_CHOICE = No
    KEYATTR = tyyppi
    UNIQUE -> SQLExecutor [INITIATOR]
SQLExecutor
    FORMAT = POSTGRES
    SQL_STATEMENT = select * from koodistot.ra_tyyppi where nimi = '@Value(tyyppi)'
    COMBINE_GEOM = Initiator Geometry Only
    EXPOSED_ATTRIBUTE_LIST = ra_tyyppi_uuid
    POSTGRES_NAMED_CONNECTION = maankayttopaatokset
    DATASET = maankayttopaatokset
    POSTGRES_SCHEMAS_FOR_TABLE_LISTING = koodistot
    COMBINE_ATTRS = Keep Result Attributes if Conflict
    POSTGRES_QUERY_FEATURE_TYPES_FOR_MERGE_FILTERS = Yes
    INITIATOR -> Tester
Tester
    TEST_CLAUSE:
      TEST ra_tyyppi_uuid ATTRIBUTE_VALUE_NULL ""
      TEST ra_tyyppi_uuid ATTRIBUTE_IS_EMPTY ""
      TEST ra_tyyppi_uuid ATTRIBUTE_IS_MISSING ""
    TEST_MODE = Automatic
    BOOL_OP = OR
    TEST_DESCRIPTION = ""
    PASSED -> UUIDGenerator
    FAILED -> FeatureMerger_3 [SUPPLIER]
UUIDGenerator
    UUID_ATTR = ra_tyyppi_uuid
    -> AttributeKeeper_6
AttributeKeeper_6
    KEEP_ATTRS = tyyppi,ra_tyyppi_uuid
    -> AttributeRenamer
    -> FeatureMerger_3 [SUPPLIER]
AttributeRenamer
    ATTR_TABLE = RENAME_SET_DEFAULT tyyppi > nimi
    -> FeatureWriter [Passed]
FeatureWriter
    POSTGRES_LOWERCASE_ATTRIBUTE_NAMES = Yes
    TOTAL_FEATURES_WRITTEN_ATTR = _total_features_written
    FORMAT = POSTGRES
    POSTGRES_TRANSACTION_INTERVAL = 1000
    POSTGRES_NAMED_CONNECTION = maankayttopaatokset
    POSTGRES_START_TRANSACTION = 0
    POSTGRES_BULK_COPY = YES
    FEATURE_TYPE_LIST_ATTR = _feature_type
    DATASET = maankayttopaatokset
    DATASET_ATTR = _dataset
    SUMMARY -> FeatureMerger_3 [SUPPLIER]
FeatureMerger_3
    MERGE_TYPE = Attributes Only
    REJECT_NULL_MISSING_KEYS = No
    PROCESS_DUPS = No
    IGNORE_NULLS = No
    ATTR_CONFLICT_RES = Use Requestor
    JOIN_KEYS = @Value(tyyppi) @Value(tyyppi) AUTO
    ATTR_ACCUM_MODE = Merge Supplier
    SUPPLIERS_FIRST = No
    MERGED -> AttributeKeeper_8

Bookmark: Muodostetaan alueista reikäkohteet ja aggrekoidaan
GeometryFilter_5
    BREAK_AGG = No
    GEOM_PORT_NAMES = Point Line Arc Area Ellipse Text
    POINT -> GeometryFilter_2_POINT_2
    LINE -> GeometryFilter_2_POINT_2
    ARC -> GeometryFilter_2_POINT_2
    AREA -> DonutBuilder_4
    ELLIPSE -> DonutBuilder_4
    TEXT -> GeometryFilter_2_POINT_2

Bookmark: Muodostetaan reikä-/saarikohteet xfm parent uuid:n perusteella
DonutBuilder_4
    CONNECT_Z_MODE = Ignore
    ALLOW_CYCLES = No
    DROP = yes
    FLAG_ATTR = _hole_flag
    GROUP_BY = igds_xfm_ref_elem_id
    AREA -> Aggregator_2
Aggregator_2
    ORDERED = No
    AGGREGATE_TYPE = Homogeneous Collection (If Possible)
    SEP = ,
    MODE = Geometry - Assemble One Level
    GROUP_BY = igds_xfm_ref_elem_id
    ACCUM_ATTRS_NAME = Use Attributes From One Feature
    AGGREGATE -> Aggregator_AGGREGATE_2

Bookmark: Alkuasetukset
GeometryFilter_2_POINT_2: Junction
    -> Aggregator_AGGREGATE_2
AttributeRenamer_12_OUTPUT: Junction
    -> AttributeFilter_4
    -> GeometryFilter_4
AttributeFilter_4
    ATTR_NAME = igds_xfm_name
    ATTR_VALUES = AK_Asemakaava,<Empty>,<Missing>,<Null>,<Unfiltered>
    AK_Asemakaava -> AttributeRenamer_9
AttributeRenamer_9
    ATTR_TABLE = RENAME_SET_DEFAULT igds_xfm_uuid > asemakaava_uuid
    -> FeatureMerger_5 [SUPPLIER]
AttributeFilter_5_AK_Asemakaava: Junction
    -> BulkAttributeRenamer_2
NullAttributeMapper_9
    ATTRLIST = lisakm2rivita vanhakohde knumerokartalle poistettava skaalattu sitova maanalainen
    OTHER_VALUE = Ohjeellinen
    NULL_TREATMENT = New Value
    ATTRCHOICE = Selected Attributes
    NEW_VALUE = FALSE
    -> NullAttributeMapper_6
NullAttributeMapper_6
    ATTRLIST = lisakm2rivita vanhakohde knumerokartalle maanalainen skaalattu poistettava sitova
    SOURCE_ATTR_VAL = Empty "Missing (Selected Attributes Only)" Null
    OTHER_VALUE = Ei
    NULL_TREATMENT = New Value
    ATTRCHOICE = Selected Attributes
    NEW_VALUE = FALSE
    -> NullAttributeMapper_7
NullAttributeMapper_7
    ATTRLIST = knumerokartalle skaalattu maanalainen vanhakohde lisakm2rivita poistettava sitova
    OTHER_VALUE = Kyllä
    NULL_TREATMENT = New Value
    ATTRCHOICE = Selected Attributes
    NEW_VALUE = TRUE
    -> NullAttributeMapper_8
NullAttributeMapper_8
    ATTRLIST = sitova
    OTHER_VALUE = Sitova
    NULL_TREATMENT = New Value
    ATTRCHOICE = Selected Attributes
    NEW_VALUE = TRUE
    -> NullAttributeMapper_10
NullAttributeMapper_10
    ATTRLIST = knumerokartalle skaalattu maanalainen vanhakohde lisakm2rivita poistettava sitova
    OTHER_VALUE = False
    NULL_TREATMENT = New Value
    ATTRCHOICE = Selected Attributes
    NEW_VALUE = FALSE
    -> GeometryFilter_3

Bookmark: Alikohteille pääkohteen uuid
Aggregator_AGGREGATE_2: Junction
    -> Tester_3
Note: Passed = alikohteet ja failed = pääkohteet
Tester_3
    TEST_CLAUSE:
      TEST @Value(igds_xfm_name) CONTAINS Sub
      TEST @Value(igds_xfm_name) = SitovanTonttijaonRengas
      TEST @Value(igds_xfm_name) = SitovanTonttijaonRengasViiva
      TEST @Value(igds_xfm_name) = Tonttinumero
      TEST @Value(igds_xfm_name) = AK_RakentaminenTekstiSymboli
    TEST_MODE = Automatic
    BOOL_OP = OR
    TEST_DESCRIPTION = ""
    PASSED -> UUIDGenerator_2
    FAILED -> UUIDGenerator_3
UUIDGenerator_3
    UUID_ATTR = igds_xfm_uuid
    -> AttributeRenamer_12_OUTPUT
    -> AttributeRenamer_12
AttributeRenamer_12
    ATTR_TABLE = RENAME_SET_DEFAULT igds_xfm_uuid > paakohde_uuid
    -> FeatureMerger [SUPPLIER]
UUIDGenerator_2
    UUID_ATTR = igds_xfm_uuid
    -> FeatureMerger [REQUESTOR]
FeatureMerger
    MERGE_TYPE = Attributes Only
    REJECT_NULL_MISSING_KEYS = No
    PROCESS_DUPS = No
    IGNORE_NULLS = No
    ATTR_CONFLICT_RES = Use Requestor
    JOIN_KEYS = @Value(igds_xfm_ref_elem_id) @Value(igds_xfm_ref_elem_id) AUTO
    ATTR_ACCUM_MODE = Merge Supplier
    SUPPLIERS_FIRST = No
    MERGED -> AttributeRenamer_12_OUTPUT

Bookmark: Poistetaan geometrittomat kohteet ja ne, joilla ei ole igds_xfm_name ominaisuudessa mitään
GeometryFilter_4
    BREAK_AGG = No
    GEOM_PORT_NAMES = Null
    <UNFILTERED> -> AttributeFilter_3
AttributeFilter_3
    ATTR_NAME = igds_xfm_name
    ATTR_VALUES = <Empty>,<Missing>,<Null>,<Unfiltered>
    <UNFILTERED> -> FeatureMerger_5 [REQUESTOR]

Bookmark: Kaikille kohteille asemakaava uuid (huom! AttributeKeeperiä ei voi käyttää ennen FeatureMergeriä)
FeatureMerger_5
    MERGE_TYPE = Attributes Only
    REJECT_NULL_MISSING_KEYS = No
    PROCESS_DUPS = No
    IGNORE_NULLS = No
    ATTR_CONFLICT_RES = Use Requestor
    JOIN_KEYS = 1 1 AUTO
    ATTR_ACCUM_MODE = Merge Supplier
    SUPPLIERS_FIRST = No
    MERGED -> AttributeFilter_5_AK_Asemakaava

Bookmark: Muutetaan ominaisuudet lowercase
BulkAttributeRenamer_2
    MODE_CHOICE = RENAME
    ATTRCHOICE = All Attributes
    CASE_CHANGE_TYPE = lower
    PATTERN_ACTION_DISP = CASECHANGE
    -> DateFormatter_2

Bookmark: Muutetaan pvm-kentät yhteensopiviksi PostGISiä varten
DateFormatter_2
    INVALID_DATE_VALUE = _FME_NO_OP_
    SRCFMT = %d.%m.%Y
    FMT = FME Date (%Y%m%d)
    DATE_ATTR = yhtluontipvm,vireilletulopvm,yhtmuokkauspvm
    -> NullAttributeMapper_9

Bookmark: Jaotellaan geometriat
GeometryFilter_3
    BREAK_AGG = No
    GEOM_PORT_NAMES = Point Line Arc Area Ellipse Text
    POINT -> Rotator
    LINE -> GeometryExtractor_2
    ARC -> GeometryExtractor_2
    AREA -> 2DForcer_8
    ELLIPSE -> 2DForcer_8
    TEXT -> CoordinateExtractor_12

Bookmark: Solujen kierron attribuutit
Rotator
    XORIG = @Value(igds_cell_insertion_x)
    YORIG = @Value(igds_cell_insertion_y)
    ANGLE = @Value(igds_rotation)
    ROTATED -> ExpressionEvaluator_2
Note: Luodaan attribuutti "angle" / Vaihdetaan kiertokulman etumerkki (SLD:n mukaiseksi)
ExpressionEvaluator_2
    VAL_ATTR = angle
    ACTION = Create New Attribute
    EXPRESSION = -(@Value(igds_rotation))
    -> TestFilter_9

Bookmark: Vanhakohde ja poistettava suodatetaan visualisointi-tauluun
TestFilter_9
    TEST_LIST:
      BOOL_OP,OR,COMPOSITE_TEST,<Unused>,TEST_CLAUSE,"TEST @Value(poistettava) = TRUE
      TEST @Value(vanhakohde) = TRUE",Visualisointi
    DEFAULT_VALUE = <UNFILTERED>
    Visualisointi -> TestFilter_Visualisointi_-__AttributeKeeper
    <UNFILTERED> -> AttributeFilter_2

Bookmark: Solut
AttributeFilter_2
    ATTR_NAME = igds_xfm_name
    ATTR_VALUES = <EMPTY>,<MISSING>,<NULL>,<UNFILTERED>,AK_RakentaminenSymboli,AK_YmparistoSymboli,AK_LiikennointiSymboli,AK_MuuAsemakaavaSymboli,AK_OmaSymboli
    <UNFILTERED> -> TestFilter_Visualisointi_-__AttributeKeeper
    AK_RakentaminenSymboli -> AttributeFilter_7_AK_RakennusalaViiva_-__SpatialFilter_Candidate
    AK_YmparistoSymboli -> AttributeFilter_2_AK_YmparistoSymboli_-__SpatialFilter_2_Candidate
    AK_LiikennointiSymboli -> AttributeFilter_7_AK_JohdoillevarattuViiva_-__AttributeKeeper_3
    AK_MuuAsemakaavaSymboli -> TestFilter_Visualisointi_-__AttributeKeeper
    AK_OmaSymboli -> AttributeFilter_7_AK_RakennusalaViiva_-__SpatialFilter_Candidate

Bookmark: Tekstien kierron attribuutit
CoordinateExtractor_12
    X_ATTR = x_origin
    Z_DEFAULT = -9999
    Z_ATTR = z_origin
    IND = 0
    MODE = Specify Coordinate
    Y_ATTR = y_origin
    -> Rotator_11
Rotator_11
    XORIG = @Value(x_origin)
    YORIG = @Value(y_origin)
    ANGLE = @Value(igds_rotation)
    ROTATED -> ExpressionEvaluator_4
Note: Luodaan attribuutti "angle" / Vaihdetaan kiertokulman etumerkki (SLD:n mukaiseksi)
ExpressionEvaluator_4
    VAL_ATTR = angle
    ACTION = Create New Attribute
    EXPRESSION = -(@Value(igds_rotation))
    -> TestFilter_8

Bookmark: Vanhakohde ja poistettava suodatetaan visualisointi-tauluun
TestFilter_8
    TEST_LIST:
      BOOL_OP,OR,COMPOSITE_TEST,<Unused>,TEST_CLAUSE,"TEST @Value(poistettava) = TRUE
      TEST @Value(vanhakohde) = TRUE",Visualisointi
    DEFAULT_VALUE = <UNFILTERED>
    Visualisointi -> TestFilter_Visualisointi_-__AttributeKeeper
    <UNFILTERED> -> AttributeFilter

Bookmark: Tekstit
AttributeFilter
    ATTR_NAME = igds_xfm_name
    ATTR_VALUES = <EMPTY>,<MISSING>,<NULL>,<UNFILTERED>,AK_AsemakaavaTeksti,AK_RakennusalaTeksti,AK_RakentaminenTeksti,AK_LiikennointiTeksti,AK_JohdoillevarattuTeksti,AK_MuuAsemakaavaTeksti,AK_OmaTeksti
    <UNFILTERED> -> TestFilter_Visualisointi_-__AttributeKeeper
    AK_AsemakaavaTeksti -> TestFilter_5
    AK_RakennusalaTeksti -> AttributeFilter_7_AK_RakennusalaViiva_-__SpatialFilter_Candidate
    AK_RakentaminenTeksti -> AttributeFilter_7_AK_RakennusalaViiva_-__SpatialFilter_Candidate
    AK_LiikennointiTeksti -> AttributeFilter_7_AK_JohdoillevarattuViiva_-__AttributeKeeper_3
    AK_JohdoillevarattuTeksti -> AttributeFilter_7_AK_JohdoillevarattuViiva_-__AttributeKeeper_3
    AK_MuuAsemakaavaTeksti -> TestFilter_2
    AK_OmaTeksti -> AttributeFilter_7_AK_JohdoillevarattuViiva_-__AttributeKeeper_3

Bookmark: AsemakaavaTeksti jako kaavamaarays ja visualisointi-tauluihin
TestFilter_5
    TEST_LIST = BOOL_OP,OR,COMPOSITE_TEST,<Unused>,TEST_CLAUSE,"TEST @Value(tyyppi) CONTAINS kaupungin nimi",Kaavamaarays
    DEFAULT_VALUE = Visualisointi
    Kaavamaarays -> AttributeFilter_7_AK_JohdoillevarattuViiva_-__AttributeKeeper_3
    Visualisointi -> TestFilter_Visualisointi_-__AttributeKeeper

Bookmark: MuuAsemakaavaTeksti jako kaavamaarays ja visualisointi tauluihin
TestFilter_2
    TEST_LIST:
      BOOL_OP,OR,COMPOSITE_TEST,<Unused>,TEST_CLAUSE,"TEST @Value(tyyppi) CONTAINS poistuva
      TEST @Value(tyyppi) CONTAINS koordinaatti",Visualisointi
    DEFAULT_VALUE = Kaavamaarays
    Visualisointi -> TestFilter_Visualisointi_-__AttributeKeeper
    Kaavamaarays -> AttributeFilter_7_AK_JohdoillevarattuViiva_-__AttributeKeeper_3

Bookmark: Korjataan viivojen geometria
GeometryExtractor_2
    REMOVE_GEOMETRY = No
    ATTR = _geometry
    KIND_LONG = GeoJSON
    -> GeometryReplacer_2
GeometryReplacer_2
    REMOVE_ATTRIBUTE = Yes
    KIND_LONG = GeoJSON
    SOURCE = @Value(_geometry)
    OGC_WKT_PRECISION_DISPLAY = 64-bit
    -> 2DForcer_6
Note: Pakotetaan 2D:ksi
2DForcer_6
    2D -> ArcFinder_kmo_Python_4
Note: Poistetaan virheelliset kaari-kohteet
ArcFinder_kmo_Python_4
    _REPLACE_SHORT_ARCS_PARAM_FMX = no
    _REMOVE_ZERO_LENGTH_LINES_PARAM_FMX = yes
    _ARCS_AFTER_REPAIR_PARAM_FMX = _arcs_after_repair
    _REPLACE_FULL_CIRCLE_ARCS_PARAM_FMX = yes
    _VERBOSE_PROBLEM_ELEM_PARAM_FMX = no
    _VERBOSE_ALL_ARC_PARAM_FMX = no
    _ARC_CURVATURE_REPORT_LIMIT_PARAM_FMX = 0.00000001
    _REPAIR_ELLIPTICAL_ARCS_PARAM_FMX = yes
    _HAS_ARCS_PARAM_FMX = _has_arcs
    _LINE_LENGTH_REPORT_LIMIT_PARAM_FMX = 0.01
    _HAS_ELLIPTICAL_ARCS_PARAM_FMX = _has_elliptical_arcs
    _REPAIR_ALL_ARCS_PARAM_FMX = yes
    _ARC_LENGTH_REPORT_LIMIT_PARAM_FMX = 0.01
    _ARCS_BEFORE_REPAIR_PARAM_FMX = _arcs_before_repair
    -> 2DForcer_7
Note: Pakotetaan 2D:ksi
2DForcer_7
    2D -> CoordinateRounder_4
Note: Pyöristetään koordinaatit 4 desimaaliin
CoordinateRounder_4
    YPREC = 4
    ZPREC = 0
    XPREC = 4
    ROUNDED -> GeometryValidator_5
Note: Validioidaan geometriat
GeometryValidator_5
    CONNECT_Z_MODE_SI = Ignore
    DUP_COORDS_CHECK_Z = No
    TYPE_REPAIR = TYPE_REPAIR
    ARC_ENDPOINT_TOLERANCE_MODE = Auto
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%SELF_INTERSECTING_PARAMS%"Yes"%PLANAR_SURFACE%PLANAR_SURFACE_PARAMS%"Yes"%SHELL_VALIDATION%SHELL_VALIDATION_PARAMS%"Yes"%SOLID_VOID_REPAIR%""%"Yes"%OGC_SIMPLE_CHECK%""%"No"%OGC_VALID_CHECK%OGC_VALID_PARAMS%"No"%MISSING_TEXTURE_COORDINATES%""%"Yes"%MISSING_VERTEX_NORMALS%""%"Yes"%AREA_ORIENTATION%ORIENTATION_CHECK_PARAMS%"Yes"
    CONNECT_Z_MODE_TR = Ignore
    NAN_REMOVAL = NAN_REMOVAL
    SELF_INTERSECTING = SELF_INTERSECTING
    NULL_REMOVAL = NULL_REMOVAL
    CHECK_HOLE_TOUCHING_POLYGON = No
    ISSUE_ATTR_NAME = _issues
    REPAIR = Yes
    SUMMARY = Detailed
    CONSECUTIVE_IDENTICAL_VERTICES_2D = CONSECUTIVE_IDENTICAL_VERTICES_2D
    PRESETS = Custom
    PASSED -> TestFilter_6
    REPAIRED -> TestFilter_6

Bookmark: Vanhakohde ja poistettava suodatetaan visualisointi-tauluun
TestFilter_6
    TEST_LIST:
      BOOL_OP,OR,COMPOSITE_TEST,<Unused>,TEST_CLAUSE,"TEST @Value(poistettava) = TRUE
      TEST @Value(vanhakohde) = TRUE",Visualisointi
    DEFAULT_VALUE = <UNFILTERED>
    Visualisointi -> TestFilter_Visualisointi_-__AttributeKeeper
    <UNFILTERED> -> AttributeFilter_7

Bookmark: AsemakaavaViiva jako kaavamaarays ja visualisointi-tauluihin
TestFilter_4
    TEST_LIST = BOOL_OP,OR,COMPOSITE_TEST,<Unused>,TEST_CLAUSE,"TEST @Value(tyyppi) CONTAINS kaupunginosan raja",Kaavamaarays
    DEFAULT_VALUE = Visualisointi
    Kaavamaarays -> AttributeFilter_7_AK_JohdoillevarattuViiva_-__AttributeKeeper_3
    Visualisointi -> TestFilter_Visualisointi_-__AttributeKeeper

Bookmark: Kohteet, joiden pitää kohdentua rakennusalalle ja jotka kirjoitetaan kaavamaarays-tauluun
AttributeFilter_7_AK_RakennusalaViiva_-__SpatialFilter_Candidate: Junction
    -> SpatialFilter [Candidate]

Bookmark: Kohteet, jotka voivat kohdentua ympäristöalueelle ja jotka kirjoitetaan kaavamaarays-tauluun
AttributeFilter_2_AK_YmparistoSymboli_-__SpatialFilter_2_Candidate: Junction
    -> SpatialFilter_2 [Candidate]

Bookmark: Muu asemakaavaviiva jako kaavamaarays ja visualisointi tauluihin
TestFilter
    TEST_LIST:
      BOOL_OP,OR,COMPOSITE_TEST,<Unused>,TEST_CLAUSE,"TEST @Value(tyyppi) CONTAINS poistuva
      TEST @Value(tyyppi) CONTAINS poistettu
      TEST @Value(tyyppi) CONTAINS viiteviiva
      TEST @Value(tyyppi) CONTAINS apuviiva",Visualisointi
    DEFAULT_VALUE = Kaavamaarays
    Visualisointi -> TestFilter_Visualisointi_-__AttributeKeeper
    Kaavamaarays -> AttributeFilter_7_AK_JohdoillevarattuViiva_-__AttributeKeeper_3

Bookmark: OmaViiva jako valitus, rakennusala ja kaavamaarays tauluihin
TestFilter_3
    TEST_LIST = BOOL_OP,OR,COMPOSITE_TEST,<Unused>,TEST_CLAUSE,"TEST @Value(tyyppi) CONTAINS valituksen",Valitus,BOOL_OP,OR,COMPOSITE_TEST,<Unused>,TEST_CLAUSE,"TEST @Value(tyyppi) CONTAINS likimääräinen",Rakennusala
    DEFAULT_VALUE = Kaavamaarays
    Valitus -> AreaBuilder
    Rakennusala -> AttributeRenamer_6_OUTPUT_-__DuplicateFilter
    Kaavamaarays -> AttributeFilter_7_AK_JohdoillevarattuViiva_-__AttributeKeeper_3

Bookmark: Kohteet, jotka menevät valitus-tauluun
TestFilter_3_Valitus_-__asemakaavat.valitus: Junction
    -> AttributeKeeper_2

Bookmark: Vallitus-taulun attribuutit
AttributeKeeper_2
    KEEP_ATTRS = asemakaava_uuid,yhtdatanomistaja,yhtluontipvm,tyyppi,yhtmuokkauspvm,igds_xfm_uuid
    -> AttributeRenamer_2
AttributeRenamer_2
    ATTR_TABLE:
      RENAME_SET_DEFAULT asemakaava_uuid > asemakaava_uuid_asemakaava
      RENAME_SET_DEFAULT igds_xfm_uuid > valitus_uuid
    -> valitus (writer POSTGIS_8)

Bookmark: valitus-taulu
valitus (writer POSTGIS_8)
    attributes: asemakaava_uuid_asemakaava uuid, valitus_uuid uuid, yhtdatanomistaja varchar(25), yhtluontipvm date, yhtmuokkauspvm date, tyyppi varchar(32)

Bookmark: Korjataan alueiden geometria
Note: Pakotetaan 2D:ksi
2DForcer_8
    2D -> ArcFinder_kmo_Python_5
Note: Poistetaan virheelliset kaari-kohteet
ArcFinder_kmo_Python_5
    _REPLACE_SHORT_ARCS_PARAM_FMX = no
    _REMOVE_ZERO_LENGTH_LINES_PARAM_FMX = yes
    _ARCS_AFTER_REPAIR_PARAM_FMX = _arcs_after_repair
    _REPLACE_FULL_CIRCLE_ARCS_PARAM_FMX = yes
    _VERBOSE_PROBLEM_ELEM_PARAM_FMX = no
    _VERBOSE_ALL_ARC_PARAM_FMX = no
    _ARC_CURVATURE_REPORT_LIMIT_PARAM_FMX = 0.00000001
    _REPAIR_ELLIPTICAL_ARCS_PARAM_FMX = yes
    _HAS_ARCS_PARAM_FMX = _has_arcs
    _LINE_LENGTH_REPORT_LIMIT_PARAM_FMX = 0.01
    _HAS_ELLIPTICAL_ARCS_PARAM_FMX = _has_elliptical_arcs
    _REPAIR_ALL_ARCS_PARAM_FMX = yes
    _ARC_LENGTH_REPORT_LIMIT_PARAM_FMX = 0.01
    _ARCS_BEFORE_REPAIR_PARAM_FMX = _arcs_before_repair
    -> CoordinateRounder_5
Note: Pyöristetään koordinaatit 4 desimaaliin
CoordinateRounder_5
    YPREC = 4
    ZPREC = 0
    XPREC = 4
    ROUNDED -> GeometryValidator_6
Note: Validioidaan geometriat
GeometryValidator_6
    DUP_COORDS_CHECK_Z = No
    TYPE_REPAIR = TYPE_REPAIR
    ARC_ENDPOINT_TOLERANCE_MODE = Auto
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%SELF_INTERSECTING_PARAMS%"Yes"%PLANAR_SURFACE%PLANAR_SURFACE_PARAMS%"Yes"%SHELL_VALIDATION%SHELL_VALIDATION_PARAMS%"Yes"%SOLID_VOID_REPAIR%""%"Yes"%OGC_SIMPLE_CHECK%""%"No"%OGC_VALID_CHECK%OGC_VALID_PARAMS%"No"%MISSING_TEXTURE_COORDINATES%""%"Yes"%MISSING_VERTEX_NORMALS%""%"Yes"%AREA_ORIENTATION%ORIENTATION_CHECK_PARAMS%"Yes"
    CONNECT_Z_MODE_TR = Ignore
    NAN_REMOVAL = NAN_REMOVAL
    NULL_REMOVAL = NULL_REMOVAL
    ISSUE_ATTR_NAME = _issues
    REPAIR = Yes
    SUMMARY = Detailed
    CONSECUTIVE_IDENTICAL_VERTICES_2D = CONSECUTIVE_IDENTICAL_VERTICES_2D
    PRESETS = Custom
    PASSED -> Orientor_2
    FAILED -> Orientor_2
    REPAIRED -> Orientor_2
Note: Muutetaan alueiden kiertosuunta oikeaksi
Orientor_2
    KIND = LEFT_HAND_RULE
    ORIENTED -> GeometryRefiner_4
GeometryRefiner_4
    -> TestFilter_7

Bookmark: Vanhakohde ja poistettava suodatetaan visualisointi-tauluun
TestFilter_7
    TEST_LIST:
      BOOL_OP,OR,COMPOSITE_TEST,<Unused>,TEST_CLAUSE,"TEST @Value(poistettava) = TRUE
      TEST @Value(vanhakohde) = TRUE",Visualisointi
    DEFAULT_VALUE = <UNFILTERED>
    Visualisointi -> TestFilter_Visualisointi_-__AttributeKeeper
    <UNFILTERED> -> AttributeFilter_8

Bookmark: Kohteet jotka menevät visualisointi-tauluun
TestFilter_Visualisointi_-__AttributeKeeper: Junction
    -> AttributeKeeper

Bookmark: Visualisointi-taulun attribuutit
AttributeKeeper
    KEEP_ATTRS = igds_cell_y_scale,sitova,yhtdatanomistaja,yhtluontipvm,tyyppi,angle,poistettava,yhtmuokkauspvm,igds_cell_x_scale,igds_xfm_uuid,teksti,igds_xfm_name,asemakaava_uuid,paakohde_uuid,vanhakohde,kerrosluku
    -> AttributeRenamer_3
AttributeRenamer_3
    ATTR_TABLE:
      RENAME_SET_DEFAULT asemakaava_uuid > asemakaava_uuid_asemakaava
      RENAME_SET_DEFAULT igds_xfm_uuid > visualisointi_uuid
      RENAME_SET_DEFAULT igds_cell_x_scale > x_scale
      RENAME_SET_DEFAULT igds_cell_y_scale > y_scale
      RENAME_SET_DEFAULT igds_xfm_name > luokka
    -> StringReplacer
StringReplacer
    CASE = NO
    FIND_TEXT = AK_
    NO_MATCH = _FME_NO_OP_
    SRC_ATTRS = luokka
    REGEXP = NO
    -> visualisointi (writer POSTGIS_9)

Bookmark: visualisointi-taulu
visualisointi (writer POSTGIS_9)
    attributes: asemakaava_uuid_asemakaava uuid, visualisointi_uuid uuid, x_scale float8, y_scale float8, luokka varchar(100), yhtdatanomistaja varchar(25), yhtluontipvm date, poistettava bool, sitova bool, kerrosluku varchar(25), vanhakohde bool, teksti varchar(254), yhtmuokkauspvm date, tyyppi varchar(100), paakohde_uuid uuid, angle float8

Bookmark: Filtteroidaan kohteet StellaMapin kohteiden mukaan
Note: AK_Tonttia ei käytetä, tontti kohteena kaavayksikkö, AK_MuuAsemakaavaAlue ja AK_OmaAlue ei käytetä
AttributeFilter_8
    ATTR_NAME = igds_xfm_name
    ATTR_VALUES = AK_Asemakaava,AK_Kayttotarkoitusalue,AK_Rakennusala,AK_KaavayksikkoAlue,AK_Tontti,AK_YmparistoAlue,AK_LiikennointiAlue,AK_Johdoillevarattualue,AK_MuuAsemakaavaAlue,AK_OmaAlue,<EMPTY>,<MISSING>,<NULL>,<UNFILTERED>
    AK_Asemakaava -> AttributeKeeper_4
    AK_Kayttotarkoitusalue -> AttributeKeeper_14
    AK_Rakennusala -> AttributeRenamer_6_OUTPUT_-__DuplicateFilter
    AK_KaavayksikkoAlue -> AttributeCreator
    AK_YmparistoAlue -> AttributeKeeper_7
    AK_LiikennointiAlue -> AttributeFilter_7_AK_JohdoillevarattuViiva_-__AttributeKeeper_3
    AK_Johdoillevarattualue -> AttributeFilter_7_AK_JohdoillevarattuViiva_-__AttributeKeeper_3

Bookmark: Kohteet, jotka kirjoitetaan kaavamaarays-tauluun, mutta eivät kohdennu millekään rakennusalalle tai ympäristöalueelle
AttributeFilter_7_AK_JohdoillevarattuViiva_-__AttributeKeeper_3: Junction
    -> AttributeKeeper_3

Bookmark: Asemakaava attribuutit
AttributeKeeper_4
    KEEP_ATTRS = kaavanlaatija,kaavanimi1,pintaala,yhtdatanomistaja,asemakaava_uuid,vireilletulopvm,kaavatyyppi,kaavanvaihe,kaavanimi2,kieli2,kuntakoodi,aluesijainti,kaavamaarayskirjasto,kieli1,yhtluontipvm,yhtmuokkauspvm
    -> asemakaava (writer POSTGIS_1)

Bookmark: asemakaava-taulu
asemakaava (writer POSTGIS_1)
    attributes: yhtdatanomistaja varchar(25), yhtluontipvm date, kaavanvaihe varchar(30), pintaala numeric(14,6), kaavanlaatija varchar(100), kaavanimi1 varchar(32), kaavatyyppi varchar(32), kieli1 varchar(15), kaavanimi2 varchar(32), kuntakoodi numeric(3,0), kieli2 varchar(15), yhtmuokkauspvm date, aluesijainti varchar(30), vireilletulopvm date, kaavamaarayskirjasto varchar(100), asemakaava_uuid uuid

Bookmark: Kayttotarkoitusalue attribuutit
AttributeKeeper_14
    KEEP_ATTRS = lisakm2rivita,korttelinnumero,kaavamerkinta,km2,kayttotarkoitus,yhtmuokkauspvm,pintaala,asemakaava_uuid,maanalainen,tyyppi,u,knumerokartalle,igds_xfm_uuid,yhtdatanomistaja,yhtluontipvm
    -> AttributeRenamer_14
AttributeRenamer_14
    ATTR_TABLE:
      RENAME_SET_DEFAULT k > kellari
      RENAME_SET_DEFAULT u > ullakko
      RENAME_SET_DEFAULT asemakaava_uuid > asemakaava_uuid_asemakaava
      RENAME_SET_DEFAULT igds_xfm_uuid > yleinen_tai_muu_alue_uuid
    -> AttributeFilter_9

Bookmark: Käyttötarkoitusalueiden jako ominaisuuden kayttotarkoitus mukaan
AttributeFilter_9
    ATTR_NAME = kayttotarkoitus
    ATTR_VALUES = Erityisalue,Virkistysalue,Suojelualue,Vesialue,MaaMetsatalousalue,MuuLiikennealue,Katualue,Kortteli tai korttelinosa,<Empty>,<Missing>,<Null>,<Unfiltered>
    Erityisalue -> AttributeCreator_2_OUTPUT
    Virkistysalue -> AttributeCreator_2_OUTPUT
    Suojelualue -> AttributeCreator_2_OUTPUT
    Vesialue -> AttributeCreator_2_OUTPUT
    MaaMetsatalousalue -> AttributeCreator_2_OUTPUT
    MuuLiikennealue -> AttributeCreator_2_OUTPUT
    Katualue -> AttributeCreator_2_OUTPUT
    Kortteli tai korttelinosa -> AttributeRenamer_4

Bookmark: yleinen_tai_muu_alue-taulu
yleinen_tai_muu_alue (writer POSTGIS_3)
    attributes: ullakko varchar(25), asemakaava_uuid_asemakaava uuid, yleinen_tai_muu_alue_uuid uuid, yhtdatanomistaja varchar(25), yhtluontipvm date, knumerokartalle bool, km2 numeric(20,10), pintaala numeric(14,6), lisakm2rivita bool, kaavamerkinta varchar(10), maanalainen bool, korttelinnumero varchar(8), kayttotarkoitus varchar(25), yhtmuokkauspvm date, tyyppi varchar(100)

Bookmark: korttelialue-taulu
korttelialue (writer POSTGIS_2)
    attributes: korttelialue_uuid uuid, ullakko varchar(25), asemakaava_uuid_asemakaava uuid, yhtdatanomistaja varchar(25), yhtluontipvm date, knumerokartalle bool, km2 numeric(20,10), pintaala numeric(14,6), lisakm2rivita bool, kaavamerkinta varchar(10), maanalainen bool, korttelinnumero varchar(8), kayttotarkoitus varchar(25), yhtmuokkauspvm date, tyyppi varchar(100)

Bookmark: Ymparistoalue
AttributeKeeper_7
    KEEP_ATTRS = igds_xfm_uuid,pintaala,asemakaava_uuid,yhtdatanomistaja,yhtluontipvm,yhtmuokkauspvm,tyyppi
    -> AttributeRenamer_7
AttributeRenamer_7
    ATTR_TABLE:
      RENAME_SET_DEFAULT igds_xfm_uuid > ymparistoalue_uuid
      RENAME_SET_DEFAULT asemakaava_uuid > asemakaava_uuid_asemakaava
    -> ymparistoalue (writer POSTGIS_4)
    -> SpatialFilter_2 [Filter]

Bookmark: ymparistoViiva ja YmparistoSymboli jotka kohdentuvat tiettyyn YmparistoAlueeseen
Note: Etsitään ympäristöalueille osuvat YmparistoViiva ja -Symboli kohteet
SpatialFilter_2
    PREDICATES = CONTAINS INTERSECTS TOUCHES
    AGGREGATE_HANDLING = Yes
    PREDATTR = _predicate
    USE_BOUNDING_BOX = No
    CURVE_BOUNDARY_RULE_PARAM = Default Rule
    PASS_CRITERIA = Pass Against One Filter
    ATTR_PREFIX = ymparistoalue_
    BASE_TYPE = Multiple Filters
    ATTR_ACCUM_MODE = Prefix Filter
    PASSED -> AttributeKeeper_3
    FAILED -> AttributeKeeper_3

Bookmark: ymparistoalue-taulu
ymparistoalue (writer POSTGIS_4)
    attributes: ymparistoalue_uuid uuid, asemakaava_uuid_asemakaava uuid, yhtdatanomistaja varchar(25), yhtluontipvm date, pintaala numeric(14,6), yhtmuokkauspvm date, tyyppi varchar(30)

Bookmark: Tontti (yhdistäminen korttelialueeseen
AttributeCreator
    ATTR_TABLE = SET_TO korttelinnumero = @Value(sijaintialue)@Value(ryhma)
    -> FeatureMerger_2 [REQUESTOR]
FeatureMerger_2
    SUPPLIER_PREFIX = kortteli_
    MERGE_TYPE = Attributes Only
    REJECT_NULL_MISSING_KEYS = No
    PROCESS_DUPS = No
    IGNORE_NULLS = No
    JOIN_KEYS = @Value(korttelinnumero) @Value(korttelinnumero) AUTO
    ATTR_ACCUM_MODE = Prefix Supplier
    SUPPLIERS_FIRST = No
    MERGED -> AttributeKeeper_11
AttributeKeeper_11
    KEEP_ATTRS = kortteli_korttelialue_uuid,igds_xfm_uuid,ryhma,pintaala,tyyppi,yksikko,u,k,tehokkuusluku,yhteensakm2,yhtluontipvm,km2,lisakm2rivita,yhtdatanomistaja,lisatietoja,lisakm2kuvaus,sitova,sijaintialue,kerrosluku,lisakm2,yhtmuokkauspvm,kunta
    -> AttributeRenamer_13
AttributeRenamer_13
    ATTR_TABLE:
      RENAME_SET_DEFAULT igds_xfm_uuid > tontti_uuid
      RENAME_SET_DEFAULT kortteli_korttelialue_uuid > korttelialue_uuid_korttelialue
      RENAME_SET_DEFAULT k > kellari
      RENAME_SET_DEFAULT u > ullakko
    -> tontti (writer POSTGIS_7)

Bookmark: tontti-taulu
tontti (writer POSTGIS_7)
    attributes: tontti_uuid uuid, korttelialue_uuid_korttelialue uuid, kellari varchar(32), ullakko varchar(32), yhtdatanomistaja varchar(25), yhtluontipvm date, sitova bool, yksikko numeric(4,0), lisakm2 float8, sijaintialue numeric(3,0), kerrosluku varchar(10), km2 float8, pintaala numeric(14,6), lisakm2kuvaus varchar(32), lisakm2rivita bool, yhteensakm2 float8, kunta numeric(3,0), tehokkuusluku float8, lisatietoja varchar(100), ryhma numeric(4,0), yhtmuokkauspvm date, tyyppi varchar(32)

Bookmark: RakennusalaViiva, RakennusalaTeksti, RakentaminenViiva, RakentaminenTeksti, RakentaminenSymboli ja OmaSymboli kohdennetaan tiettyyn rakennusalaan
Note: Etsitään rakennusalalle osuvat rakennusalat
SpatialFilter
    PREDICATES = CONTAINS INTERSECTS TOUCHES
    AGGREGATE_HANDLING = Yes
    PREDATTR = _predicate
    USE_BOUNDING_BOX = No
    CURVE_BOUNDARY_RULE_PARAM = Default Rule
    PASS_CRITERIA = Pass Against One Filter
    ATTR_PREFIX = rakennusala_
    BASE_TYPE = Multiple Filters
    ATTR_ACCUM_MODE = Prefix Filter
    PASSED -> AttributeKeeper_3

Bookmark: Kaavamaarayskohteiden attribuutit
AttributeKeeper_3
    KEEP_ATTRS = igds_cell_y_scale,sitova,yhtdatanomistaja,yhtluontipvm,tyyppi,rakennusala_igds_xfm_uuid,angle,yhtmuokkauspvm,igds_cell_x_scale,igds_xfm_uuid,ymparistoalue_ymparistoalue_uuid,maanalainen,teksti,igds_xfm_name,asemakaava_uuid
    -> AttributeRenamer_8
AttributeRenamer_8
    ATTR_TABLE:
      RENAME_SET_DEFAULT asemakaava_uuid > asemakaava_uuid_asemakaava
      RENAME_SET_DEFAULT igds_xfm_name > luokka
      RENAME_SET_DEFAULT rakennusala_igds_xfm_uuid > rakennusala_uuid_rakennusala
      RENAME_SET_DEFAULT igds_xfm_uuid > kaavamaarays_uuid
      RENAME_SET_DEFAULT igds_cell_x_scale > x_scale
      RENAME_SET_DEFAULT igds_cell_y_scale > y_scale
      RENAME_SET_DEFAULT ymparistoalue_ymparistoalue_uuid > ymparistoalue_uuid_ymparistoalue
    -> StringReplacer_2
StringReplacer_2
    CASE = NO
    FIND_TEXT = AK_
    NO_MATCH = _FME_NO_OP_
    SRC_ATTRS = luokka
    REGEXP = NO
    -> kaavamaarays (writer POSTGIS_6)

Bookmark: kaavamaarays-taulu
kaavamaarays (writer POSTGIS_6)
    attributes: asemakaava_uuid_asemakaava uuid, luokka varchar(100), rakennusala_uuid_rakennusala uuid, kaavamaarays_uuid uuid, yhtdatanomistaja varchar(25), yhtluontipvm date, sitova bool, maanalainen bool, teksti varchar(100), yhtmuokkauspvm date, tyyppi varchar(100), x_scale float8, y_scale float8, angle float8

Bookmark: Rakennusala
AttributeKeeper_8
    KEEP_ATTRS = sitova,varisavy,yhtdatanomistaja,yhtluontipvm,tyyppi,yhtmuokkauspvm,igds_xfm_uuid,lisakm2rivita,maanalainen,ra_tyyppi_uuid,u,pintaala,asemakaava_uuid,kerrosluku,km2
    -> AttributeRenamer_5
AttributeRenamer_5
    ATTR_TABLE:
      RENAME_SET_DEFAULT u > ullakko
      RENAME_SET_DEFAULT igds_xfm_uuid > rakennusala_uuid
      RENAME_SET_DEFAULT asemakaava_uuid > asemakaava_uuid_asemakaava
      RENAME_SET_DEFAULT ra_tyyppi_uuid > ra_tyyppi_uuid_ra_tyyppi
    -> rakennusala (writer POSTGIS_5)

Bookmark: rakennusala-taulu
rakennusala (writer POSTGIS_5)
    attributes: ullakko varchar(25), rakennusala_uuid uuid, asemakaava_uuid_asemakaava uuid, yhtdatanomistaja varchar(25), yhtluontipvm date, sitova bool, kerrosluku varchar(25), km2 numeric(20,10), pintaala numeric(14,6), lisakm2rivita bool, maanalainen bool, varisavy varchar(25), yhtmuokkauspvm date, tyyppi varchar(35), ra_tyyppi_uuid_ra_tyyppi uuid

FME custom transformer DonutHoleFilter
This transformer removes holes from donut polygons that are less than the user defined size. Non-donut features are left untouched.
Set the Minimum Hole Area to the desired size. All holes less than this size will be removed. If all holes are removed the feature will be demoted to a simple polygon.
This transformer will not modify any polygons that occupy the donut holes, but an AreaCalculator and Tester can be used to remove those as well.

Parameters:
- FILTER =   # Minimum Hole Area

INPUT (input)
    -> ParameterFetcher
Note: Fetch filter size
ParameterFetcher
    ATTR_LIST = _FILTER {$(FILTER)}
    -> PythonCaller_3
Note: Remove small holes
PythonCaller_3
    PYTHONSOURCE:
      import fmeobjects
      # Template Function interface:
      def removeSmallHoles(feature):
          gtype = feature.getAttribute('fme_geometry')
          filter = feature.getAttribute('_FILTER')
          # only process donuts
          if gtype == 'fme_donut':
              geom = feature.getGeometry()
              # create new donut geometry from outershell
              newgeom = fmeobjects.FMEDonut(geom.getOuterBoundaryAsCurve())
              # loop through inner shells
              for x in range(geom.numInnerBoundaries()):
                  boundary = geom.getInnerBoundaryAsCurveAt(x)
                  # create polygon to measure area
                  poly = fmeobjects.FMEPolygon(boundary)
                  area = poly.getArea()
                  # if shell is large enough copy to new donut geometry
                  if area > float(filter):
                      newgeom.addInnerBoundaryCurve(boundary)

              # replace old geometry with new
              feature.setGeometry(newgeom)
    PYTHONSYMBOL = removeSmallHoles
    -> GeometryRefiner
Note: If all holes removed, / revert to polygon
GeometryRefiner
    -> AttributeRemover
Note: Clean up feature
AttributeRemover
    REMOVE_ATTRS = _FILTER
    -> OUTPUT (output)
OUTPUT (output)
